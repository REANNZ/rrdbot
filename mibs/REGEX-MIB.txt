REGEX-MIB DEFINITIONS ::= BEGIN

IMPORTS
    MODULE-IDENTITY, OBJECT-TYPE, Counter64, Integer32,
    TimeTicks, Unsigned32
    FROM SNMPv2-SMI
    begemot
    FROM BEGEMOT-MIB;

regexData MODULE-IDENTITY
    LAST-UPDATED "200603290000Z"
    ORGANIZATION "Nate Nielsen"
    CONTACT-INFO "nielsen@memberwesb.com"
    DESCRIPTION "The MIB for the bsnmp-regex."

    ::= { begemot 203 }

-- --------------------------------------------------------------------------

regexCount OBJECT-TYPE
    SYNTAX Integer32
    MAX-ACCESS read-only
    STATUS  current
    DESCRIPTION "Number of regexEntry objects."
    ::= { regexData 0 }

regexEntry OBJECT IDENTIFIER
    ::= { regexData 1 }

--
-- entry information
--

regexIndex OBJECT-TYPE
    SYNTAX Integer32
    MAX-ACCESS read-only
    STATUS current
    DESCRIPTION "Index of this regexEntry object."
    ::= { regexEntry 1 }

regexDescr OBJECT-TYPE
    SYNTAX OCTET STRING
    MAX-ACCESS read-only
    STATUS current
    DESCRIPTION "Description of the regexEntry object."
    ::= { regexEntry 2 }

regexLast OBJECT-TYPE
    SYNTAX TimeTicks
    UNITS "1/100th of a Second"
    MAX-ACCESS read-only
    STATUS current
    DESCRIPTION "Last time this the regexEntry counters were updated."
    ::= { regexEntry 3 }

regexInteger OBJECT-TYPE
    SYNTAX Integer32
    MAX-ACCESS read-only
    STATUS current
    DESCRIPTION "Integer value of this regexEntry object."
    ::= { regexEntry 4 }

regexString OBJECT-TYPE
    SYNTAX OCTET STRING
    MAX-ACCESS read-only
    STATUS current
    DESCRIPTION "String value of this regexEntry object."
    ::= { regexEntry 5 }

END
