--
-- Copyright (c) 2008
--   Stefan Walter <stef@memberwebs.com>
--
-- Redistribution and use in source and binary forms, with or without
-- modification, are permitted provided that the following conditions
-- are met:
-- 1. Redistributions of source code must retain the above copyright
--    notice, this list of conditions and the following disclaimer.
-- 2. Redistributions in binary form must reproduce the above copyright
--    notice, this list of conditions and the following disclaimer in the
--    documentation and/or other materials provided with the distribution.
--
-- THIS SOFTWARE IS PROVIDED BY AUTHOR AND CONTRIBUTORS ``AS IS'' AND
-- ANY EXPRESS OR IMPLIED WARRANTIES, INCLUDING, BUT NOT LIMITED TO, THE
-- IMPLIED WARRANTIES OF MERCHANTABILITY AND FITNESS FOR A PARTICULAR PURPOSE
-- ARE DISCLAIMED.  IN NO EVENT SHALL AUTHOR OR CONTRIBUTORS BE LIABLE
-- FOR ANY DIRECT, INDIRECT, INCIDENTAL, SPECIAL, EXEMPLARY, OR CONSEQUENTIAL
-- DAMAGES (INCLUDING, BUT NOT LIMITED TO, PROCUREMENT OF SUBSTITUTE GOODS
-- OR SERVICES; LOSS OF USE, DATA, OR PROFITS; OR BUSINESS INTERRUPTION)
-- HOWEVER CAUSED AND ON ANY THEORY OF LIABILITY, WHETHER IN CONTRACT, STRICT
-- LIABILITY, OR TORT (INCLUDING NEGLIGENCE OR OTHERWISE) ARISING IN ANY WAY
-- OUT OF THE USE OF THIS SOFTWARE, EVEN IF ADVISED OF THE POSSIBILITY OF
-- SUCH DAMAGE.
--
PCAP-MIB DEFINITIONS ::= BEGIN

IMPORTS
    MODULE-IDENTITY, OBJECT-TYPE, Counter64, Integer32, TimeTicks, Unsigned32
    FROM SNMPv2-SMI
    begemot
    FROM BEGEMOT-MIB;

pcap MODULE-IDENTITY
    LAST-UPDATED "200903010000Z"
    ORGANIZATION "Stef Walter"
    CONTACT-INFO "stef@memberwebs.com"
    DESCRIPTION "The MIB for the bsnmp-pcap module."

    ::= { begemot 206 }

-- --------------------------------------------------------------------------

pcapCount  OBJECT-TYPE
    SYNTAX Integer32
    MAX-ACCESS read-only
    STATUS current
    DESCRIPTION "The number network monitors."
    ::= { pcap 1 }

pcapTable OBJECT-TYPE
    SYNTAX SEQUENCE OF PcapEntry
    MAX-ACCESS not-accessible
    STATUS current
    DESCRIPTION "A list of entries representing network monitors. The number of entries is given by the value of jailCount."
    ::= { pcap 2 }

pcapEntry OBJECT-TYPE
    SYNTAX PcapEntry
    MAX-ACCESS not-accessible
    STATUS current
    DESCRIPTION "An entry containing information about a network monitor."
    INDEX { pcapIndex }
    ::= { pcapTable 1 }

PcapEntry ::=
    SEQUENCE {
        pcapIndex Integer32,
        pcapDescr OCTET STRING,
        pcapDevice OCTET STRING,
        pcapFilter OCTET STRING,
        pcapOctets Counter64,
        pcapPackets Counter64,
    }

pcapIndex OBJECT-TYPE
    SYNTAX Integer32
    MAX-ACCESS read-only
    STATUS current
    DESCRIPTION "Index of this pcapEntry."
    ::= { pcapEntry 0 }

pcapDescr OBJECT-TYPE
    SYNTAX OCTET STRING
    MAX-ACCESS read-only
    STATUS current
    DESCRIPTION "A readable description of this network monitor."
    ::= { pcapEntry 1 }

pcapDevice OBJECT-TYPE
    SYNTAX OCTET STRING
    MAX-ACCESS read-only
    STATUS current
    DESCRIPTION "The device network traffic is being monitored on."
    ::= { pcapEntry 2 }

pcapFilter OBJECT-TYPE
    SYNTAX OCTET STRING
    MAX-ACCESS read-only
    STATUS current
    DESCRIPTION "The (tcpdump style) filter for traffic to monitor."
    ::= { pcapEntry 3 }

pcapOctets OBJECT-TYPE
    SYNTAX Counter64
    MAX-ACCESS read-only
    STATUS current
    DESCRIPTION "Number of octets seen by the network monitor."
    ::= { pcapEntry 10 }

pcapPackets OBJECT-TYPE
    SYNTAX Counter64
    MAX-ACCESS read-only
    STATUS current
    DESCRIPTION "Number of packets seen by the network monitor."
    ::= { pcapEntry 11 }

END
